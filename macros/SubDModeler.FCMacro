# SubD Modeler: opens the modeler without switching workbench.
# Edits the selected SubD object, otherwise opens the modeler in object mode. Requires the SubD Modeler addon to be installed.
import subd_modeler
subd_modeler.start()
